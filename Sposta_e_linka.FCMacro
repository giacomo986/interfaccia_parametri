selectedObjs = FreeCADGui.Selection.getSelection()[0]

nome = selectedObjs.Label

Documento_originale = App.ActiveDocument

Documento_nuovo = App.newDocument(nome)

Documento_nuovo.saveAs("/home/giacomo/%s.FCStd" % nome)

corpo = Documento_nuovo.moveObject(selectedObjs, True)

Documento_nuovo.saveAs("/home/giacomo/%s.FCStd" % nome)

Documento_originale.addObject('App::Link',nome).setLink(corpo)
